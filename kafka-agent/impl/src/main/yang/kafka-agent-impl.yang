/* ***********************************************************************************************************
* Copyright (c) 2016 Cisco and/or its affiliates.
* This software is licensed to you under the terms of the Apache License, Version 2.0 (the "License").
* You may obtain a copy of the License at http://www.apache.org/licenses/LICENSE-2.0
* The code, technical concepts, and all information contained herein, are the property of Cisco Technology, Inc.
* and/or its affiliated entities, under various laws including copyright, international treaties, patent,
* and/or contract. Any use of the material herein must be in accordance with the terms of the License.
* All rights not expressly granted by the License are reserved.
* Unless required by applicable law or agreed to separately in writing, software distributed under the
* License is distributed on an "AS IS" BASIS, WITHOUT WARRANTIES OR CONDITIONS OF ANY KIND,
* either express or implied.

* Name:       Kafka-agent-impl.yang
* Purpose:    Kafka agent implementation yang model
************************************************************************************************************ */

module kafka-agent-impl {
    yang-version 1;
    namespace "urn:opendaylight:params:xml:ns:yang:kafka-agent:impl";
    prefix "kafka-agent-impl";

    import config { prefix config; revision-date 2013-04-05; }
    import opendaylight-md-sal-binding { prefix md-sal-binding; revision-date 2013-10-28;}
    import opendaylight-md-sal-dom { prefix md-sal-dom; revision-date 2013-10-28;}

    description
        "Service definition for kafka-agent project";

    revision "2015-09-22" {
        description
            "Initial revision";
    }

    identity kafka-agent {
        base config:module-type;
        config:java-name-prefix Kafka;
    }

    augment "/config:modules/config:module/config:configuration" {
        case kafka-agent {
            when "/config:modules/config:module/config:type = 'kafka-agent'";
            container binding-broker {
                uses config:service-ref {
                    refine type {
                        mandatory true;
                        config:required-identity md-sal-binding:binding-broker-osgi-registry;
                    }
                }
            }
            container dom-broker {
                uses config:service-ref {
                    refine type {
                        mandatory true;
                        config:required-identity md-sal-dom:dom-broker-osgi-registry;
                     }
                }
             }
        }
    }
}
